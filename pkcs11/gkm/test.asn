TEST { }

DEFINITIONS EXPLICIT TAGS ::=

BEGIN

TestIntegers ::= SEQUENCE {
	mpi                     INTEGER
}

TestData ::= SEQUENCE {
	data			OCTET STRING,
	boolean                 BOOLEAN DEFAULT FALSE
}

TestStringMpi ::= SEQUENCE {
	mpi                     OCTET STRING
}

TestBitString ::= SEQUENCE {
	data                     BIT STRING
}

TestOid ::= SEQUENCE {
	oid                     OBJECT IDENTIFIER
}

END
